# Dataset_4

# Specification: Dataset_4

## R1
- Type: FR
- Requirement: It is possible to â€œlikeâ€ a certain event.

## R2
- Type: MN
- Requirement: All changes updates and additions to the WCS system shall be updated in the WCS Developer and WCS User Guides. Every change must be reflected in WCS system documentation

## R3
- Type: F
- Requirement: The system shall have a MDI form that allows for the viewing of the graph and the data table.

## R4
- Type: US
- Requirement: Every registered user will have access to the product s support site via the Internet. 70% of registered users shall find a solution to their problem within 5 minutes of using the support site.

## R5
- Type: PE
- Requirement: The product shall provide Multi-threading and Load Balancing.The product shall provide multi-threading technology as well as load balancing to overcome data load spikes and traffic.

## R6
- Type: SE
- Requirement: Only valid data shall be entered into the system. No invalid data shall be entered into the system.

## R7
- Type: NFR
- Requirement: Application portability DESC: The application should be portable with iOS and Android.

## R8
- Type: FR
- Requirement: Select Spanish as preferred language Given the administrator wants to select a preferred language When the administrator selects Spanish as a new language Then the web-portal will show all text in Spanish

## R9
- Type: US
- Requirement: The application shall ask the user to confirm dropping a player or trading a player before performing the action.

## R10
- Type: US
- Requirement: All CCR users shall receive training before the WCS system is deployed. One training session will be held for 100% of CCR users before system deployment (based on a CCR user being available)

## R11
- Type: SE
- Requirement: The system shall have basic data integrity checking to reduce the possibility of incorrect or invalid data being introduced.

## R12
- Type: PE
- Requirement: The search results shall be returned no later 30 seconds after the user has entered the search criteria

## R13
- Type: A
- Requirement: The RFS system should be available 24/7 especially during the budgeting period. The RFS system shall be available 90% of the time all year and 98% during the budgeting period. 2% of the time the system will become available within 1 hour of the time that the situation is reported.

## R14
- Type: US
- Requirement: 90% of untrained realtors shall be able to install the product on their device without printed instructions

## R15
- Type: SC
- Requirement: The WCS system shall have the ability to connect other designated WCS databases currently not included in the system.

## R16
- Type: FR
- Requirement: The from-location can be selected on the map.

## R17
- Type: FR
- Requirement: Update Page with link to sites nearby

## R18
- Type: F
- Requirement: The current repair facility ratings shall be displayed to the user.

## R19
- Type: FR
- Requirement: Editing information Given the restaurant owner is logged in And information exists When the restaurant owner edits information Then the information should be edited

## R20
- Type: A
- Requirement: The product shall adhere to the corporate online availability schedule. The application is brought down only within 98% of the scheduled outages per the availability schedule.

## R21
- Type: NFR
- Requirement: The graphical user interface of SplitPay is to be designed with usability as the first priority. The app will be presented and organized in a manner that is both visually appealing and easy for the user to navigate. There will be feedbacks and visual cues such as notifications to inform users of updates and pop-ups to provide users with instructions.

## R22
- Type: MN
- Requirement: The product must be highly configurable for use with various database management systems for the end users. 80% of end users are able to integrate new database management systems with the product without changing the product s software code.

## R23
- Type: US
- Requirement: The WCS system shall use appropriate nomenclature and terminology as defined by the Corporate Community Grants organization. All interfaces and reports will undergo usability tests by CCR users.

## R24
- Type: FR
- Requirement: It is possible to â€œtweetâ€ a certain news item.

## R25
- Type: LF
- Requirement: The interface shall be appealing to callers and supervisors. In the interface and usability survey 80% of beta testers must report that the interface is appealing.

## R26
- Type: FR
- Requirement: In this case, user can add the items he/she likes to his cart by touching â€œAdd to the cartâ€ button.

## R27
- Type: F
- Requirement: The product shall be able to delete room equipment.

## R28
- Type: FR
- Requirement: The language can only be selected in the main app.

## R29
- Type: F
- Requirement: The Disputes System shall accurately provide a list of possible reason codes for a given transaction. The list of possible reason codes must be derived based on the type of transaction and the industry that the merchant belongs to according to the business rules defined for the Disputes System.

## R30
- Type: PE
- Requirement: The system shall refresh the display every 60 seconds.

## R31
- Type: FR
- Requirement: Build Ajax Response to update home page with a link to nearby site based on user location

## R32
- Type: NFR
- Requirement: Application testability DESC: Test environments should be built for the application to allow testing of the applications different functions.

## R33
- Type: FR
- Requirement: The administrator can add edges of a path which is used in the route planner.

## R34
- Type: SC
- Requirement: The product shall be able to process all transactions.The product shall process minimum of 1 million transactions per year.

## R35
- Type: MN
- Requirement: The WCS system must run queries to the WCS databases once again (on a specified day) to update the available data available to CCR users. Queries must be made to external databases for data refresh once a week.

## R36
- Type: F
- Requirement: The system shall offer the ability to pause and resume the refresh of data.

## R37
- Type: LF
- Requirement: When a shot is marked as a hit the product shall simulate the sound of a shot hitting its target.

## R38
- Type: O
- Requirement: A primary database will be used to store cached data for active users.

## R39
- Type: FR
- Requirement: Mobile application - Search by specific dish DESC: A user should be able to select a specific dish in a given list as input. The result is displayed in a map view by default.

## R40
- Type: FR
- Requirement: user is able to search items. User can search items according to their price,
  their location, their category.

## R41
- Type: FR
- Requirement: The user can select a topic from the search result described in requirement UCAR703.

## R42
- Type: F
- Requirement: System shall automatically update the main page of the website every Friday and show the 4 latest movies that have been added to the website.

## R43
- Type: NFR
- Requirement: Users must be a Radford University student in order to access the automatic class schedule and assignment sharing features of this application Users can authenticate by logging in using their RU username and password.

## R44
- Type: FR
- Requirement: The main menu contains a launcher to the News-app.3.1.4

## R45
- Type: F
- Requirement: The system shall allow modification of the display.

## R46
- Type: US
- Requirement: Users shall be able to reach the add drop and trade player pages with one click from the team owner s page.

## R47
- Type: PE
- Requirement: The System shall allow for a minimum of 6 users to work at the same time.

## R48
- Type: NFR
- Requirement: There are no safety requirements with this application, other than any normal hazards of a mobile device. The only hazard is a user using the device when they should not be, such as while driving.

## R49
- Type: FR
- Requirement: A search described in requirements UCAR203 results in a displayed set of POIâ€™s that match the search input.

## R50
- Type: NFR
- Requirement: The average time for the server to respond, over the question testing set, will be less than or equal to 2 seconds.

## R51
- Type: SE
- Requirement: The product shall ensure that it can only be accessed by authorized users. The product will be able to distinguish between authorized and unauthorized users in all access attempts

## R52
- Type: FR
- Requirement: The only events that are available in the agenda-app are extracted from the agenda RSS-feeds in the selected language.

## R53
- Type: O
- Requirement: 98% of the user workstations shall meet the minimum software requirements prior to implementation

## R54
- Type: FR
- Requirement: Mobile application - Search by destination DESC: A user should be able to input a maximum and a minimum distance, according to his/her position. By default the minimum distance is set to 0 km and the maximum to 10 km. The user should be able to input a higher or lower maximum distance and a higher minimum distance than set by default. The result is displayed in a map view by default.

## R55
- Type: SC
- Requirement: The product shall be able to handle up to 1500 simultaneous users. The system shall perform with 1500 users as a time.

## R56
- Type: F
- Requirement: When both players have positioned their 5 ships on their defensive grids the product shall define the status of each player for the first turn.

## R57
- Type: PE
- Requirement: Staff members shall be able to complete a set of tasks in a timely manner.

## R58
- Type: NFR
- Requirement: The information and the search methods of the Studenthandbook-app are restricted depending on file format of the handbook-information.

## R59
- Type: FR
- Requirement: This unit will have a list of generic words related specifically to potential queries (examples: building, professor)

## R60
- Type: NFR
- Requirement: SplitPay will not affect data stored outside of its servers nor will it affect any other applications installed on the userâ€™s phone. It cannot cause any damage to the phone or its internal components. The only potential safety concern associated with this application applies to virtually all handset apps: SplitPay should not be used while operating a vehicle or in any other situation where the userâ€™s attention must be focused elsewhere.

## R61
- Type: FT
- Requirement: 100% of saved user preferences shall be restored when system comes back online.

## R62
- Type: F
- Requirement: The leads washing functionality will use the parameters supplied by corporate and schools to score part of the lead.

## R63
- Type: F
- Requirement: The audit report shall be available to other adjusters at later points in time.

## R64
- Type: F
- Requirement: For each shot the product shall examine the defensive grid of the defensive player to determine whether the shot was a hit or miss.

## R65
- Type: FR
- Requirement: It is possible to search for events by subject.

## R66
- Type: O
- Requirement: The Disputes application shall interface with the Statement Database. The Statement Database provides the transaction details to the Disputes System. All transaction details must be obtained from the Statement Database

## R67
- Type: FR
- Requirement: A search described in requirements UCAR406 and UCAR407 results in a displayed set of events that match the search input.

## R68
- Type: FR
- Requirement: In this case, if the user no longer wishes to use the system, he/she can click â€œDelete Profileâ€ button. After deleting the profile, the user will no longer be able to use the system with the account details that he entered before.

## R69
- Type: NFR
- Requirement: Security The connection between the Web API and the programs will use HTTPS, for security.

## R70
- Type: F
- Requirement: The system shall display clear property images in the search results

## R71
- Type: F
- Requirement: The user shall select to view the preferred repair facility ratings.

## R72
- Type: FR
- Requirement: when user clicks on links to browse sites from home page, the system should respond with a list of links to all the sites by A-Z, sorted on site name

## R73
- Type: F
- Requirement: The estimator shall search by zipcode with a radius of 30 miles if no parts are found for the preferred parts suppliers

## R74
- Type: LF
- Requirement: The website should appeal to all Africans not only Nigerians.

## R75
- Type: A
- Requirement: The product shall be available 24 hours per day seven days per week.

## R76
- Type: F
- Requirement: The system shall filter data by

## R77
- Type: FR
- Requirement: The administrator can link a POI to a certain building, floor and room.

## R78
- Type: LF
- Requirement: The message board shall contain the 5 most recently posted messages on the league page. The messages will contain up to the first 150 characters of the message.

## R79
- Type: PE
- Requirement: Customer shall be able to check the status of their prepaid card by entering in the PIN number in under 5 seconds.

## R80
- Type: NFR
- Requirement: Agenda is restricted to what is available in the feeds on the list of agenda RSS-feeds.

## R81
- Type: FR
- Requirement: Based on the selection the product categories will be listed: Outerwear,Soft Shell,Fleece,Knits,Wovens,Active Wear, Safety,Accessories,Team Wear, e.c.o. Collection

## R82
- Type: FR
- Requirement: user touches log out button, and logs out of the system. The user will not use
  the system until he/she logs in again.

## R83
- Type: US
- Requirement: The system shall be used by realtors with no training.

## R84
- Type: SC
- Requirement: The website shall be capable of supporting 100 000 customers.

## R85
- Type: FR
- Requirement: The product will be able to delete conference rooms.

## R86
- Type: O
- Requirement: We must be able to interface with any HTML browser.

## R87
- Type: FR
- Requirement: The changes will apply if the user clicks on the link in the email.

## R88
- Type: FR
- Requirement: The route planned by the navigator is shown in the map view.

## R89
- Type: SE
- Requirement: The system shall only be accessed by authorized Corporate Community Grants (CCR) employees. Users must be authenticated using their IBM intranet user name and password.

## R90
- Type: LF
- Requirement: When a shot is marked as a miss the product shall simulate the sound of a shot missing its target.

## R91
- Type: FR
- Requirement: The client will send a GET request to the Web API with the question as a URL parameter The client will specify the header Content-Type: application/json in their requests as convention. A valid API query is a single URL parameter containing one sentence that is a question in standard English.

## R92
- Type: O
- Requirement: The product shall be able to be installed in the specified environment within 1 working day.

## R93
- Type: NFR
- Requirement: Fast Response The average time for the server to respond, over the question testing set, will be less than or equal to 2 seconds

## R94
- Type: MN
- Requirement: The product shall be updated on a regular basis.The product will have a new major feature introduced every six months and quarterly maintenance releases every six months.

## R95
- Type: PE
- Requirement: The response time of general student management tasks shall take no longer than 5 seconds and the response time of schedule generation shall take no longer than 30 seconds.

## R96
- Type: O
- Requirement: The product will be available for licensing as a one-server two-five servers or five-or-more servers license.

## R97
- Type: NFR
- Requirement: A new user will make less than 3 mistakes in 5 minutes after 5 minutes of use.

## R98
- Type: FR
- Requirement: This unit will query the database for data about the elements in the mapping

## R99
- Type: LF
- Requirement: The website shall not be offensive to religious or ethnic groups.

## R100
- Type: FR
- Requirement: The administrator can modify the list of TU/e related Twitter-sites.
